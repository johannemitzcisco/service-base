module device {
  namespace "http://com/example/device";
  prefix device;

  import tailf-ncs { prefix ncs; }
  import node { prefix node; }

  grouping device-grouping {
    uses node:node-grouping;

    list role {
      key name;
      leaf name {
        type leafref {
          path "/device:device-role/device:name";
        }
      }
      list template-variables {
        key template-name;
        leaf template-name {
          type leafref {
            path "deref(../../name)/../device:device-template/device:name";
          }
        }
        list variable {
          key name;
          leaf name {
            type leafref {
              path "deref(../../template-name)/../device:variable-name";
            }
          }
          leaf value {
            type string;
          }
        }
      }
    }
  }

  list device-role {
    key name;
    leaf name {
      type string;
    }
    list device-template {
      key name;
      leaf name {
        type leafref {
          path "/ncs:devices/ncs:template/ncs:name";
        }
      }
      leaf ned-id {
        type leafref {
          path "deref(../name)/../ncs:ned-id/ncs:id";
        }
      }
      leaf-list variable-name {
        type string;
      }
    }
  }
}
