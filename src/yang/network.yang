module network {
  namespace "http://com/example/network";
  prefix network;

  import tailf-ncs { prefix ncs; }
  import tailf-common { prefix tailf; }
  import ietf-inet-types { prefix inet; }
  
  grouping network-allocation-grouping {
    leaf name {
      type string;
    }
    leaf first-address {
      config "false";
      type string;
    }
    leaf last-address {
      config "false";
      type string;
    }
    tailf:action allocate-ip-addresses {
      tailf:actionpoint service-base-allocateIPAddresses-action;
      input {
        leaf allocating-service {
          type string;
        }
        leaf address-count {
          type uint8;
        }
      }
      output {
        leaf result {
          type string;
        }
      }
    }
    tailf:action check-ready {
      tailf:actionpoint service-base-checkReady-action;
      output {
        leaf result {
          type string;
        }
      }
    }
  }

  grouping network-grouping {
    tailf:action initialize-ip-address-pool {
      tailf:actionpoint service-base-initializeIPAddressPool-action;
      input {
      }
      output {
        leaf result {
          type string;
        }
      }
    }
    leaf name {
      type string;
    }
    leaf network {
      tailf:info "Subnet (x.x.x.x), ex. 192.168.1.0";
      type inet:ipv4-address;
      mandatory "true";
    }
    leaf netmask {
      tailf:info "Subnet Mask (x.x.x.x), ex. 255.255.255.0";
      type inet:ipv4-address;
      mandatory "true";
    }
    leaf prefix {
      type uint8 {
        range "1..32";
      }
    }
    leaf gateway-ip-address {
      tailf:info "Gateway IP address";
      type inet:ipv4-address;
    }
    leaf vlan-id {
      type uint16 {
        range "1..4096";
      }
    }
    container resource-pool {
      tailf:info "Resource Pool for IP addresses";
      leaf name {
        type string;
      }
      list range {
        key "from to";
        leaf from {
          type inet:ip-address-no-zone;
        }

        leaf to {
          type inet:ip-address-no-zone;
        }
      }
      list subnet {
        key "address cidrmask";
        leaf address {
          type inet:ip-address;
        }

        leaf cidrmask {
          type uint8 {
            range "1..128";
          }
        }
      }
      list allocation {
        config "false";
        key name;
        uses network-allocation-grouping;
      }
    }
    leaf-list dns-ip-address {
      tailf:info "DNS server IP address";
      type inet:ipv4-address;
    }
  }
}
